-- MIB Module Name ~~~~~~~~~~~~~~~~~~~~~~~~~~~~~~~~~~~~~~~~~~~~~~~~~~~~~~~~~~~~~
BLG-MIB DEFINITIONS ::= BEGIN

-- Imported Items ~~~~~~~~~~~~~~~~~~~~~~~~~~~~~~~~~~~~~~~~~~~~~~~~~~~~~~~~~~~~~~
    IMPORTS
        enterprises, IpAddress, TimeTicks, OBJECT-TYPE, mib-2,
                MODULE-IDENTITY, NOTIFICATION-TYPE,
                OBJECT-IDENTITY, Integer32, Counter32
            FROM SNMPv2-SMI
		
        TEXTUAL-CONVENTION, RowStatus
            FROM SNMPv2-TC;

blgMibModule MODULE-IDENTITY
    LAST-UPDATED "201707101100Z"
    ORGANIZATION ""
    CONTACT-INFO ""
    DESCRIPTION "MIB information for Batt LG Chem"
  ::= { mib-2 1 }

-- Type Assignments ~~~~~~~~~~~~~~~~~~~~~~~~~~~~~~~~~~~~~~~~~~~~~~~~~~~~~~~~~~~~
Signed8 ::= TEXTUAL-CONVENTION
  STATUS current
  DESCRIPTION ""
  SYNTAX Integer32 ( -128..127 )

Signed16 ::= TEXTUAL-CONVENTION
  STATUS current
  DESCRIPTION ""
  SYNTAX Integer32 ( -32768..32767 )

Signed32 ::= TEXTUAL-CONVENTION
  STATUS current
  DESCRIPTION ""
  SYNTAX Integer32 ( -2147483648..2147483647 )

Unsigned8 ::= TEXTUAL-CONVENTION
  STATUS current
  DESCRIPTION ""
  SYNTAX Integer32 ( 0..255 )

Unsigned16 ::= TEXTUAL-CONVENTION
  STATUS current
  DESCRIPTION ""
  SYNTAX Integer32 ( 0..65535 )
  
Boolean ::= TEXTUAL-CONVENTION
  STATUS current
  DESCRIPTION ""
  SYNTAX INTEGER { false(0), true(1) }

Float ::= TEXTUAL-CONVENTION
  STATUS current
  DESCRIPTION ""
  SYNTAX Integer32 ( -2147483648..2147483647 )

TimeIntervalInSeconds ::= TimeTicks

TimeIntervalInMinutes ::= Integer32

TimeIntervalInDays ::= Integer32

Access-Level ::= INTEGER {
  read-only(1),
  read-Write(2)
}

Enable-State ::= INTEGER {
  disabled(0),
  enabled(1)
}

Severity-Level ::= INTEGER {
  warnings-And-Above(1),
  minor-And-Above(2),
  major-And-Above(3),
  none(4),
  critical-only(5)
}

SNMP-Trap-Version ::= INTEGER {
  snmp-V1-Trap(0),
  snmp-V2-Trap(1),
  snmp-V3-Trap(2)
}

Trap-Receiver-Mode ::= INTEGER {
  normal-Traps(1),
  acknowledged-Summary-Trap(2)
}

Alarm-Active-State ::= INTEGER {
  not-Active(0),
  active-Warning(1),
  active-Minor(2),
  active-Major(3),
  active-Critical(4),
  reserved(5)
}

Trap-Alarm-Keep-Severity ::= INTEGER {
  critical(1),
  major(2),
  minor(3),
  warning(4),
  cleared(5)
}

Alarm-Severity ::= INTEGER {
  disabled(0),
  critical(1),
  major(2),
  minor(3),
  warning(4),
  control(5)
}

System-Alarm ::= INTEGER {
	ac-Main-Fail(1),
	ac-Low-Voltage(2),
	dc-Low-Voltage(3),
	rectifier-Fail(4),
	rectifier-Current-Limit(5),
	rectifier-Short-Circuit(6),
	rectifier-Over-Temperature(7),
	dcDc1-Alarm(8),
	dcDc2-Alarm(9),
	dcDc3-Alarm(10),
	dcDc4-Alarm(11),
	dcDc5-Alarm(12),
	dcDc6-Alarm(13)
}

Active-State ::= INTEGER {
  closed(0),
  open(1)
}

Status-State ::= INTEGER {
  normal(0),
  lower-Limit(1),
  upper-Limit(2),
  other-Error(3)
}

YesNo-State ::= INTEGER {
  no(0),
  yes(1)
}

OnOff-State ::= INTEGER {
  off(0),
  on(1)
}

String-10 ::= TEXTUAL-CONVENTION
    STATUS       current
    DESCRIPTION  ""
    SYNTAX       OCTET STRING (SIZE(0..10))

String-20 ::= TEXTUAL-CONVENTION
    STATUS       current
    DESCRIPTION  ""
    SYNTAX       OCTET STRING (SIZE(0..20))

String-30 ::= TEXTUAL-CONVENTION
    STATUS       current
    DESCRIPTION  ""
    SYNTAX       OCTET STRING (SIZE(0..30))

String-40 ::= TEXTUAL-CONVENTION
    STATUS       current
    DESCRIPTION  ""
    SYNTAX       OCTET STRING (SIZE(0..40))

String-60 ::= TEXTUAL-CONVENTION
    STATUS       current
    DESCRIPTION  ""
    SYNTAX       OCTET STRING (SIZE(0..60))

MIB-Object-ID ::= TEXTUAL-CONVENTION
    STATUS       current
    DESCRIPTION  ""
    SYNTAX       OCTET STRING (SIZE(0..80))

String-253 ::= TEXTUAL-CONVENTION
    STATUS       current
    DESCRIPTION  ""
    SYNTAX       OCTET STRING (SIZE(0..253))

No-Data ::= TEXTUAL-CONVENTION
  STATUS current
  DESCRIPTION ""
  SYNTAX OCTET STRING(SIZE(0))

-- OID Value Assignment and OBJECT-TYPE Construct ~~~~~~~~~~~~~~~~~~~~~~~~~~~~
stu OBJECT IDENTIFIER ::= { enterprises 47865 }
ems OBJECT IDENTIFIER ::= { stu 3 }
blg OBJECT IDENTIFIER ::= { ems 30 }

blg-Objects OBJECT-IDENTITY
  STATUS current
  DESCRIPTION ""
 ::= { blg 10 }

system-Identity OBJECT-IDENTITY
  STATUS current
  DESCRIPTION ""
 ::= { blg-Objects 10 }

serial-Number OBJECT-TYPE
  SYNTAX String-10
  MAX-ACCESS read-only
  STATUS current
  DESCRIPTION "The system serial number assigned by the manufacturer."
  DEFVAL { "0000000000" }
::= { system-Identity 10 }

site-Id OBJECT-TYPE
  SYNTAX String-20
  MAX-ACCESS read-write
  STATUS current
  DESCRIPTION "site identity"
  DEFVAL { "" }
::= { system-Identity 20 }

site-Name OBJECT-TYPE
  SYNTAX String-40
  MAX-ACCESS read-write
  STATUS current
  DESCRIPTION "The site name."
  DEFVAL { "" }
::= { system-Identity 30 }

site-Address OBJECT-TYPE
  SYNTAX String-40
  MAX-ACCESS read-write
  STATUS current
  DESCRIPTION "The site address."
  DEFVAL { "" }
::= { system-Identity 40 }

system-Username OBJECT-TYPE
  SYNTAX String-20
  MAX-ACCESS read-write
  STATUS current
  DESCRIPTION ""
  DEFVAL { "admin" }
::= { system-Identity 50 }

system-Password OBJECT-TYPE
  SYNTAX String-20
  MAX-ACCESS read-write
  STATUS current
  DESCRIPTION ""
  DEFVAL { "admin" }
::= { system-Identity 60 }

software-Version OBJECT-TYPE
  SYNTAX String-10
  MAX-ACCESS read-only
  STATUS current
  DESCRIPTION "software version."
  DEFVAL { "1.0" }
::= { system-Identity 70 }


communications OBJECT-IDENTITY
  STATUS current
  DESCRIPTION ""
 ::= { blg-Objects 20 }

ip-Address OBJECT-TYPE
  SYNTAX IpAddress
  MAX-ACCESS read-write
  STATUS current
  DESCRIPTION "The Internet Protocol (IP) address. This value and the Subnet Mask must be set correctly to communicate using Ethernet. Consult your network administrator."
  DEFVAL { "1.1.1.1" }
::= { communications 10 }

subnet-Mask OBJECT-TYPE
  SYNTAX IpAddress
  MAX-ACCESS read-write
  STATUS current
  DESCRIPTION "Identifies which fragment of the IP address is the sub-network identity. This value and the IP Address must be set correctly to communicate using Ethernet. Consult your network administrator."
  DEFVAL { "255.255.255.0" }
::= { communications 20 }

gateway-Address OBJECT-TYPE
  SYNTAX IpAddress
  MAX-ACCESS read-write
  STATUS current
  DESCRIPTION "Allows access to IP addresses outside your sub-network. Consult your network administrator."
  DEFVAL { "1.1.1.1" }
::= { communications 30 }


snmp OBJECT-IDENTITY
  STATUS current
  DESCRIPTION ""
 ::= { communications 40 }

snmp-Read-Community OBJECT-TYPE
  SYNTAX String-20
  MAX-ACCESS read-write
  STATUS current
  DESCRIPTION "Community that can get items."
  DEFVAL { "public" }
::= { snmp 10 }

snmp-Write-Community OBJECT-TYPE
  SYNTAX String-20
  MAX-ACCESS read-write
  STATUS current
  DESCRIPTION "Community that can set items."
  DEFVAL { "private" }
::= { snmp 20 }

enable-Trap-Repeat OBJECT-TYPE
  SYNTAX Enable-State
  MAX-ACCESS read-write
  STATUS current
  DESCRIPTION "If enabled, alarm activation traps will be repeated according to Trap Repeat Rate."
  DEFVAL { enabled }
::= { snmp 30 }

trap-Repeat-Times OBJECT-TYPE
  SYNTAX INTEGER
  UNITS ""
  MAX-ACCESS read-write
  STATUS current
  DESCRIPTION "How many times the trap will be sent."
  DEFVAL { 1 }
::= { snmp 40 }

trap-Repeat-Rate OBJECT-TYPE
  SYNTAX TimeIntervalInMinutes
  UNITS "minutes"
  MAX-ACCESS read-write
  STATUS current
  DESCRIPTION "How often to send a trap to trap receivers if Enable Trap Repeat is Enabled or the trap receiver's Trap Receiver Mode is Acknowledged Summary Trap."
  DEFVAL { 5 }
::= { snmp 50 }

snmp-Trap-Receiver-Table OBJECT-TYPE
  SYNTAX SEQUENCE OF SNMP-Trap-Receiver-Entry
  MAX-ACCESS not-accessible
  STATUS current
  DESCRIPTION ""
::= { snmp 60 }

snmp-Trap-Receiver-Entry OBJECT-TYPE
  SYNTAX SNMP-Trap-Receiver-Entry
  MAX-ACCESS not-accessible
  STATUS current
  DESCRIPTION ""
  INDEX  { snmp-Trap-Receiver-Index }
::= { snmp-Trap-Receiver-Table 1 }

SNMP-Trap-Receiver-Entry ::= SEQUENCE {
  snmp-Trap-Receiver-Index Unsigned8,
  trap-Receiver-IP-Address IpAddress,
  trap-Receiver-Port Unsigned16,
  trap-Receiver-Name String-20,
  trap-Receiver-Level Severity-Level,
  trap-Receiver-Community String-20,
  trap-Receiver-Mode Trap-Receiver-Mode,
  acknowledge-Alarm-Summary-Trap No-Data
}

snmp-Trap-Receiver-Index OBJECT-TYPE
  SYNTAX Unsigned8
  MAX-ACCESS read-only
  STATUS current
  DESCRIPTION "Automatically generated index object."
::= { snmp-Trap-Receiver-Entry 1 }


trap-Receiver-IP-Address OBJECT-TYPE
  SYNTAX IpAddress
  MAX-ACCESS read-write
  STATUS current
  DESCRIPTION "SNMP notifications of events are sent to this IP address."
  DEFVAL { "1.1.1.1" }
::= { snmp-Trap-Receiver-Entry 20 }

trap-Receiver-Port OBJECT-TYPE
  SYNTAX Unsigned16
  MAX-ACCESS read-write
  STATUS current
  DESCRIPTION "SNMP notifications of events are sent to this UDP port."
  DEFVAL { 162 }
::= { snmp-Trap-Receiver-Entry 30 }

trap-Receiver-Name OBJECT-TYPE
  SYNTAX String-20
  MAX-ACCESS read-write
  STATUS current
  DESCRIPTION "Name used to identify the receiver."
  DEFVAL { "" }
::= { snmp-Trap-Receiver-Entry 40 }

trap-Receiver-Level OBJECT-TYPE
  SYNTAX Severity-Level
  MAX-ACCESS read-write
  STATUS current
  DESCRIPTION "Sets the severity of alarms to be reported to this trap receiver."
  DEFVAL { none }
::= { snmp-Trap-Receiver-Entry 50 }

trap-Receiver-Community OBJECT-TYPE
  SYNTAX String-20
  MAX-ACCESS read-write
  STATUS current
  DESCRIPTION "Community to use for traps sent to the receiver."
  DEFVAL { "public" }
::= { snmp-Trap-Receiver-Entry 60 }

trap-Receiver-Mode OBJECT-TYPE
  SYNTAX Trap-Receiver-Mode
  MAX-ACCESS read-write
  STATUS current
  DESCRIPTION "Set to Normal traps to send normal traps to a Network Management System on alarm activation and deactivation. Set to Acknowledged Summary Traps to send summary traps to PowerManagerII. These traps are repeated until PowerManagerII receives the trap, connects to the controller, and downloads alarms and data."
  DEFVAL { normal-Traps }
::= { snmp-Trap-Receiver-Entry 70 }

acknowledge-Alarm-Summary-Trap OBJECT-TYPE
  SYNTAX No-Data
  MAX-ACCESS read-write
  STATUS current
  DESCRIPTION "This command will acknowledge reception of the alarm summary trap."
::= { snmp-Trap-Receiver-Entry 80 }



outBack OBJECT-IDENTITY
  STATUS current
  DESCRIPTION ""
::= { blg-Objects 30 }

outBack-Total OBJECT-TYPE
  SYNTAX INTEGER
  MAX-ACCESS read-only
  STATUS current
  DESCRIPTION "Total out back. Default 10"
::= { outBack 10 }

outBack-Table OBJECT-TYPE
  SYNTAX SEQUENCE OF OutBack-Entry
  MAX-ACCESS not-accessible
  STATUS current
  DESCRIPTION ""
::= { outBack 20 }

outBack-Entry OBJECT-TYPE
  SYNTAX OutBack-Entry
  MAX-ACCESS not-accessible
  STATUS current
  DESCRIPTION ""
  INDEX  { outBack-Index }
::= { outBack-Table 1 }

OutBack-Entry ::= SEQUENCE {
	outBack-Index INTEGER,
	pv-Voltage INTEGER,
	pv-Current INTEGER,
	batt-Voltage INTEGER,
	batt-Current INTEGER,
	aux-Mode INTEGER,
	error-Mode INTEGER,
	charger-Mode INTEGER,
	daily-Kah INTEGER
}

outBack-Index OBJECT-TYPE
  SYNTAX INTEGER
  MAX-ACCESS not-accessible
  STATUS current
  DESCRIPTION "out Back index."
::= { outBack-Entry 1 }

pv-Voltage OBJECT-TYPE
  SYNTAX INTEGER
  MAX-ACCESS read-only
  STATUS current
  DESCRIPTION ""
::= { outBack-Entry 2 }

pv-Current OBJECT-TYPE
  SYNTAX INTEGER
  MAX-ACCESS read-only
  STATUS current
  DESCRIPTION ""
::= { outBack-Entry 3 }

batt-Voltage OBJECT-TYPE
  SYNTAX INTEGER
  MAX-ACCESS read-only
  STATUS current
  DESCRIPTION ""
::= { outBack-Entry 4 }

batt-Current OBJECT-TYPE
  SYNTAX INTEGER
  MAX-ACCESS read-only
  STATUS current
  DESCRIPTION ""
::= { outBack-Entry 5 }

aux-Mode OBJECT-TYPE
  SYNTAX INTEGER ( 0..1 )
  MAX-ACCESS read-only
  STATUS current
  DESCRIPTION ""
::= { outBack-Entry 6 }

error-Mode OBJECT-TYPE
  SYNTAX INTEGER ( 0..1 )
  MAX-ACCESS read-only
  STATUS current
  DESCRIPTION ""
::= { outBack-Entry 7 }

charger-Mode OBJECT-TYPE
  SYNTAX INTEGER ( 0..1 )
  MAX-ACCESS read-only
  STATUS current
  DESCRIPTION ""
::= { outBack-Entry 8 }

daily-Kah OBJECT-TYPE
  SYNTAX INTEGER
  MAX-ACCESS read-only
  STATUS current
  DESCRIPTION ""
::= { outBack-Entry 9 }




battery OBJECT-IDENTITY
  STATUS current
  DESCRIPTION ""
::= { blg-Objects 40 }

battery-Total OBJECT-TYPE
  SYNTAX INTEGER
  MAX-ACCESS read-only
  STATUS current
  DESCRIPTION "Total battery system. Default 7"
::= { battery 10 }

battery-Table OBJECT-TYPE
  SYNTAX SEQUENCE OF Battery-Entry
  MAX-ACCESS not-accessible
  STATUS current
  DESCRIPTION ""
::= { battery 20 }

battery-Entry OBJECT-TYPE
  SYNTAX Battery-Entry
  MAX-ACCESS not-accessible
  STATUS current
  DESCRIPTION ""
  INDEX  { battery-Index }
::= { battery-Table 1 }

Battery-Entry ::= SEQUENCE {
	battery-Index INTEGER,
	alarm-Flag-System INTEGER,
	warning-Flag-System INTEGER,
	fault-Flag-System INTEGER,
	batt-Pack-Alarm-Address INTEGER,
	batt-Pack-Warning-Address INTEGER,
	batt-Pack-Fault-Address INTEGER,
	average-Voltage-System INTEGER,
	total-Current-System INTEGER,
	soc-System INTEGER,
	soh-System INTEGER,
	lowest-Cell-Voltage-On-System INTEGER,
	lowest-Cell-Voltage-Pack-Address INTEGER,
	highest-Cell-Voltage-On-System INTEGER,
	highest-Cell-Voltage-Pack-Address INTEGER,
	lowest-Temp-On-System INTEGER,
	lowest-Temp-Pack-Address INTEGER,
	highest-Temp-On-System INTEGER,
	highest-Temp-Pack-Address INTEGER,
	current-Limit-Charging-System INTEGER,
	current-Limit-Discharging-System INTEGER,
	max-Current-Limit-Charging-Pack INTEGER,
	max-Current-Limit-Discharging-Pack INTEGER,
	number-Online-Battery-Pack INTEGER,
	number-Of-Cell-In-Pack INTEGER
}

battery-Index OBJECT-TYPE
  SYNTAX INTEGER
  MAX-ACCESS not-accessible
  STATUS current
  DESCRIPTION "battery index."
::= { battery-Entry 1 }

alarm-Flag-System OBJECT-TYPE
  SYNTAX INTEGER ( 0..1 )
  MAX-ACCESS read-only
  STATUS current
  DESCRIPTION ""
::= { battery-Entry 2 }

warning-Flag-System OBJECT-TYPE
  SYNTAX INTEGER ( 0..1 )
  MAX-ACCESS read-only
  STATUS current
  DESCRIPTION ""
::= { battery-Entry 3 }

fault-Flag-System OBJECT-TYPE
  SYNTAX INTEGER ( 0..1 )
  MAX-ACCESS read-only
  STATUS current
  DESCRIPTION ""
::= { battery-Entry 4 }

batt-Pack-Alarm-Address OBJECT-TYPE
  SYNTAX INTEGER ( 0..9 )
  MAX-ACCESS read-only
  STATUS current
  DESCRIPTION ""
::= { battery-Entry 5 }

batt-Pack-Warning-Address OBJECT-TYPE
  SYNTAX INTEGER ( 0..9 )
  MAX-ACCESS read-only
  STATUS current
  DESCRIPTION ""
::= { battery-Entry 6 }

batt-Pack-Fault-Address OBJECT-TYPE
  SYNTAX INTEGER ( 0..9 )
  MAX-ACCESS read-only
  STATUS current
  DESCRIPTION ""
::= { battery-Entry 7 }

average-Voltage-System OBJECT-TYPE
  SYNTAX INTEGER
  MAX-ACCESS read-only
  STATUS current
  DESCRIPTION ""
::= { battery-Entry 8 }

total-Current-System OBJECT-TYPE
  SYNTAX INTEGER
  MAX-ACCESS read-only
  STATUS current
  DESCRIPTION ""
::= { battery-Entry 9 }

soc-System OBJECT-TYPE
  SYNTAX INTEGER
  MAX-ACCESS read-only
  STATUS current
  DESCRIPTION ""
::= { battery-Entry 10 }

soh-System OBJECT-TYPE
  SYNTAX INTEGER
  MAX-ACCESS read-only
  STATUS current
  DESCRIPTION ""
::= { battery-Entry 11 }

lowest-Cell-Voltage-On-System OBJECT-TYPE
  SYNTAX INTEGER
  MAX-ACCESS read-only
  STATUS current
  DESCRIPTION ""
::= { battery-Entry 12 }

lowest-Cell-Voltage-Pack-Address OBJECT-TYPE
  SYNTAX INTEGER ( 1..10 )
  MAX-ACCESS read-only
  STATUS current
  DESCRIPTION ""
::= { battery-Entry 13 }

highest-Cell-Voltage-On-System OBJECT-TYPE
  SYNTAX INTEGER ( 0..1 )
  MAX-ACCESS read-only
  STATUS current
  DESCRIPTION ""
::= { battery-Entry 14 }

highest-Cell-Voltage-Pack-Address OBJECT-TYPE
  SYNTAX INTEGER ( 1..10 )
  MAX-ACCESS read-only
  STATUS current
  DESCRIPTION ""
::= { battery-Entry 15 }

lowest-Temp-On-System OBJECT-TYPE
  SYNTAX INTEGER
  MAX-ACCESS read-only
  STATUS current
  DESCRIPTION ""
::= { battery-Entry 16 }

lowest-Temp-Pack-Address OBJECT-TYPE
  SYNTAX INTEGER ( 1..10 )
  MAX-ACCESS read-only
  STATUS current
  DESCRIPTION ""
::= { battery-Entry 17 }

highest-Temp-On-System OBJECT-TYPE
  SYNTAX INTEGER
  MAX-ACCESS read-only
  STATUS current
  DESCRIPTION ""
::= { battery-Entry 18 }

highest-Temp-Pack-Address OBJECT-TYPE
  SYNTAX INTEGER ( 1..10 )
  MAX-ACCESS read-only
  STATUS current
  DESCRIPTION ""
::= { battery-Entry 19 }

current-Limit-Charging-System OBJECT-TYPE
  SYNTAX INTEGER
  MAX-ACCESS read-only
  STATUS current
  DESCRIPTION ""
::= { battery-Entry 20 }

current-Limit-Discharging-System OBJECT-TYPE
  SYNTAX INTEGER
  MAX-ACCESS read-only
  STATUS current
  DESCRIPTION ""
::= { battery-Entry 21 }

max-Current-Limit-Charging-Pack OBJECT-TYPE
  SYNTAX INTEGER
  MAX-ACCESS read-only
  STATUS current
  DESCRIPTION ""
::= { battery-Entry 22 }

max-Current-Limit-Discharging-Pack OBJECT-TYPE
  SYNTAX INTEGER
  MAX-ACCESS read-only
  STATUS current
  DESCRIPTION ""
::= { battery-Entry 23 }

number-Online-Battery-Pack OBJECT-TYPE
  SYNTAX INTEGER
  MAX-ACCESS read-only
  STATUS current
  DESCRIPTION ""
::= { battery-Entry 24 }

number-Of-Cell-In-Pack OBJECT-TYPE
  SYNTAX INTEGER
  MAX-ACCESS read-only
  STATUS current
  DESCRIPTION ""
::= { battery-Entry 25 }



pack OBJECT-IDENTITY
  STATUS current
  DESCRIPTION ""
::= { blg-Objects 50 }

pack-Total OBJECT-TYPE
  SYNTAX INTEGER
  MAX-ACCESS read-only
  STATUS current
  DESCRIPTION "Total pack of battery. Default 70"
::= { pack 10 }

pack-Table OBJECT-TYPE
  SYNTAX SEQUENCE OF Pack-Entry
  MAX-ACCESS not-accessible
  STATUS current
  DESCRIPTION ""
::= { pack 20 }

pack-Entry OBJECT-TYPE
  SYNTAX Pack-Entry
  MAX-ACCESS not-accessible
  STATUS current
  DESCRIPTION ""
  INDEX  { battery-Index, pack-Index }
::= { pack-Table 1 }

Pack-Entry ::= SEQUENCE {
	pack-Index INTEGER,
	hardware-Bms-Version INTEGER,
	software-Bms-Version INTEGER,
	alarm-Flag-System-Pack INTEGER,
	warning-Flag-System-Pack INTEGER,
	fault-Flag-System-Pack INTEGER,
	soc-Pack INTEGER,
	soh-Pack INTEGER,
	voltage-Pack INTEGER,
	current-Pack INTEGER,
	lowest-Cell-Voltage-Pack INTEGER,
	highest-Cell-Voltage-Pack INTEGER,
	average-Cell-Voltage-Pack INTEGER,
	current-Limit-Charging-Pack INTEGER,
	current-Limit-Discharging-Pack INTEGER,
	average-Temp-Pack INTEGER,
	target-Cell-For-Balancing INTEGER,
	number-Of-Recharge-Cycle INTEGER,
	design-Capacity-Of-Battery-Pack INTEGER,
	usable-Capacity-Of-Battery-Pack INTEGER,
	remaining-Capacity-Of-Battery-Pack INTEGER
}

pack-Index OBJECT-TYPE
  SYNTAX INTEGER
  MAX-ACCESS not-accessible
  STATUS current
  DESCRIPTION "battery pack index."
::= { pack-Entry 1 }

hardware-Bms-Version OBJECT-TYPE
  SYNTAX INTEGER ( 0..1 )
  MAX-ACCESS read-only
  STATUS current
  DESCRIPTION ""
::= { pack-Entry 2 }

software-Bms-Version OBJECT-TYPE
  SYNTAX INTEGER ( 0..1 )
  MAX-ACCESS read-only
  STATUS current
  DESCRIPTION ""
::= { pack-Entry 3 }

alarm-Flag-System-Pack OBJECT-TYPE
  SYNTAX INTEGER ( 0..1 )
  MAX-ACCESS read-only
  STATUS current
  DESCRIPTION ""
::= { pack-Entry 4 }

warning-Flag-System-Pack OBJECT-TYPE
  SYNTAX INTEGER ( 0..1 )
  MAX-ACCESS read-only
  STATUS current
  DESCRIPTION ""
::= { pack-Entry 5 }

fault-Flag-System-Pack OBJECT-TYPE
  SYNTAX INTEGER ( 0..1 )
  MAX-ACCESS read-only
  STATUS current
  DESCRIPTION ""
::= { pack-Entry 6 }

soc-Pack OBJECT-TYPE
  SYNTAX INTEGER
  MAX-ACCESS read-only
  STATUS current
  DESCRIPTION "%"
::= { pack-Entry 7 }

soh-Pack OBJECT-TYPE
  SYNTAX INTEGER
  MAX-ACCESS read-only
  STATUS current
  DESCRIPTION "%"
::= { pack-Entry 8 }

voltage-Pack OBJECT-TYPE
  SYNTAX INTEGER
  MAX-ACCESS read-only
  STATUS current
  DESCRIPTION "V"
::= { pack-Entry 9 }

current-Pack OBJECT-TYPE
  SYNTAX INTEGER
  MAX-ACCESS read-only
  STATUS current
  DESCRIPTION "A"
::= { pack-Entry 10 }

lowest-Cell-Voltage-Pack OBJECT-TYPE
  SYNTAX INTEGER
  MAX-ACCESS read-only
  STATUS current
  DESCRIPTION "V"
::= { pack-Entry 11 }

highest-Cell-Voltage-Pack OBJECT-TYPE
  SYNTAX INTEGER
  MAX-ACCESS read-only
  STATUS current
  DESCRIPTION "V"
::= { pack-Entry 12 }

average-Cell-Voltage-Pack OBJECT-TYPE
  SYNTAX INTEGER
  MAX-ACCESS read-only
  STATUS current
  DESCRIPTION "V"
::= { pack-Entry 13 }

current-Limit-Charging-Pack OBJECT-TYPE
  SYNTAX INTEGER
  MAX-ACCESS read-only
  STATUS current
  DESCRIPTION "A"
::= { pack-Entry 14 }

current-Limit-Discharging-Pack OBJECT-TYPE
  SYNTAX INTEGER
  MAX-ACCESS read-only
  STATUS current
  DESCRIPTION "A"
::= { pack-Entry 15 }

average-Temp-Pack OBJECT-TYPE
  SYNTAX INTEGER
  MAX-ACCESS read-only
  STATUS current
  DESCRIPTION "C"
::= { pack-Entry 16 }

target-Cell-For-Balancing OBJECT-TYPE
  SYNTAX INTEGER ( 0..14 )
  MAX-ACCESS read-only
  STATUS current
  DESCRIPTION ""
::= { pack-Entry 17 }

number-Of-Recharge-Cycle OBJECT-TYPE
  SYNTAX INTEGER
  MAX-ACCESS read-only
  STATUS current
  DESCRIPTION "Times"
::= { pack-Entry 18 }

design-Capacity-Of-Battery-Pack OBJECT-TYPE
  SYNTAX INTEGER
  MAX-ACCESS read-only
  STATUS current
  DESCRIPTION "Ah"
::= { pack-Entry 19 }

usable-Capacity-Of-Battery-Pack OBJECT-TYPE
  SYNTAX INTEGER
  MAX-ACCESS read-only
  STATUS current
  DESCRIPTION "Ah"
::= { pack-Entry 20 }

remaining-Capacity-Of-Battery-Pack OBJECT-TYPE
  SYNTAX INTEGER
  MAX-ACCESS read-only
  STATUS current
  DESCRIPTION "Ah"
::= { pack-Entry 21 }



-- traps
blg-Traps OBJECT-IDENTITY
  STATUS current
  DESCRIPTION ""
::= { blg 60 }

blg-Outback-Traps OBJECT-IDENTITY
  STATUS current
  DESCRIPTION ""
::= { blg-Traps 100 }

shorted-Battery-Sensor-Active-Traps NOTIFICATION-TYPE
  OBJECTS { outBack-Index }
  STATUS current
  DESCRIPTION ""
::= { blg-Outback-Traps 101 }

shorted-Battery-Sensor-Inactive-Traps NOTIFICATION-TYPE
  OBJECTS { outBack-Index }
  STATUS current
  DESCRIPTION ""
::= { blg-Outback-Traps 102 }

too-Hot-Active-Traps NOTIFICATION-TYPE
  OBJECTS { outBack-Index }
  STATUS current
  DESCRIPTION ""
::= { blg-Outback-Traps 103 }

too-Hot-Inactive-Traps NOTIFICATION-TYPE
  OBJECTS { outBack-Index }
  STATUS current
  DESCRIPTION ""
::= { blg-Outback-Traps 104 }

high-Voc-Active-Traps NOTIFICATION-TYPE
  OBJECTS { outBack-Index }
  STATUS current
  DESCRIPTION ""
::= { blg-Outback-Traps 105 }

high-Voc-Inactive-Traps NOTIFICATION-TYPE
  OBJECTS { outBack-Index }
  STATUS current
  DESCRIPTION ""
::= { blg-Outback-Traps 106 }



blg-Pack-Traps OBJECT-IDENTITY
  STATUS current
  DESCRIPTION ""
::= { blg-Traps 200 }

batt-Cell-Over-Voltage-Active-Traps NOTIFICATION-TYPE
  OBJECTS { battery-Index, pack-Index }
  STATUS current
  DESCRIPTION ""
::= { blg-Pack-Traps 201 }

batt-Cell-Over-Voltage-Inactive-Traps NOTIFICATION-TYPE
  OBJECTS { battery-Index, pack-Index }
  STATUS current
  DESCRIPTION ""
::= { blg-Pack-Traps 202 }

batt-Cell-Under-Voltage-Active-Traps NOTIFICATION-TYPE
  OBJECTS { battery-Index, pack-Index }
  STATUS current
  DESCRIPTION ""
::= { blg-Pack-Traps 203 }

batt-Cell-Under-Voltage-Inactive-Traps NOTIFICATION-TYPE
  OBJECTS { battery-Index, pack-Index }
  STATUS current
  DESCRIPTION ""
::= { blg-Pack-Traps 204 }

over-Charging-Current-Active-Traps NOTIFICATION-TYPE
  OBJECTS { battery-Index, pack-Index }
  STATUS current
  DESCRIPTION ""
::= { blg-Pack-Traps 205 }

over-Charging-Current-Inactive-Traps NOTIFICATION-TYPE
  OBJECTS { battery-Index, pack-Index }
  STATUS current
  DESCRIPTION ""
::= { blg-Pack-Traps 206 }

over-Discharging-Current-Active-Traps NOTIFICATION-TYPE
  OBJECTS { battery-Index, pack-Index }
  STATUS current
  DESCRIPTION ""
::= { blg-Pack-Traps 207 }

over-Discharging-Current-Inactive-Traps NOTIFICATION-TYPE
  OBJECTS { battery-Index, pack-Index }
  STATUS current
  DESCRIPTION ""
::= { blg-Pack-Traps 208 }

batt-Temperature-Above-Upper-Limit-Active-Traps NOTIFICATION-TYPE
  OBJECTS { battery-Index, pack-Index }
  STATUS current
  DESCRIPTION ""
::= { blg-Pack-Traps 209 }

batt-Temperature-Above-Upper-Limit-Inactive-Traps NOTIFICATION-TYPE
  OBJECTS { battery-Index, pack-Index }
  STATUS current
  DESCRIPTION ""
::= { blg-Pack-Traps 210 }

batt-Temperature-Below-Lower-Limit-Active-Traps NOTIFICATION-TYPE
  OBJECTS { battery-Index, pack-Index }
  STATUS current
  DESCRIPTION ""
::= { blg-Pack-Traps 211 }

batt-Temperature-Below-Lower-Limit-Inactive-Traps NOTIFICATION-TYPE
  OBJECTS { battery-Index, pack-Index }
  STATUS current
  DESCRIPTION ""
::= { blg-Pack-Traps 212 }

soc-Above-Upper-Limit-Active-Traps NOTIFICATION-TYPE
  OBJECTS { battery-Index, pack-Index }
  STATUS current
  DESCRIPTION ""
::= { blg-Pack-Traps 213 }

soc-Above-Upper-Limit-Inactive-Traps NOTIFICATION-TYPE
  OBJECTS { battery-Index, pack-Index }
  STATUS current
  DESCRIPTION ""
::= { blg-Pack-Traps 214 }

voltage-Different-Active-Traps NOTIFICATION-TYPE
  OBJECTS { battery-Index, pack-Index }
  STATUS current
  DESCRIPTION ""
::= { blg-Pack-Traps 215 }

voltage-Different-Inactive-Traps NOTIFICATION-TYPE
  OBJECTS { battery-Index, pack-Index }
  STATUS current
  DESCRIPTION ""
::= { blg-Pack-Traps 216 }

temperature-Different-Active-Traps NOTIFICATION-TYPE
  OBJECTS { battery-Index, pack-Index }
  STATUS current
  DESCRIPTION ""
::= { blg-Pack-Traps 217 }

temperature-Different-Inactive-Traps NOTIFICATION-TYPE
  OBJECTS { battery-Index, pack-Index }
  STATUS current
  DESCRIPTION ""
::= { blg-Pack-Traps 218 }

END

-- MIB Module Name ~~~~~~~~~~~~~~~~~~~~~~~~~~~~~~~~~~~~~~~~~~~~~~~~~~~~~~~~~~~~~
STN-MIB DEFINITIONS ::= BEGIN

-- Imported Items ~~~~~~~~~~~~~~~~~~~~~~~~~~~~~~~~~~~~~~~~~~~~~~~~~~~~~~~~~~~~~~
    IMPORTS
        enterprises, IpAddress, TimeTicks, OBJECT-TYPE, mib-2,
                MODULE-IDENTITY, NOTIFICATION-TYPE,
                OBJECT-IDENTITY, Integer32, Counter32
            FROM SNMPv2-SMI
		
        TEXTUAL-CONVENTION, RowStatus
            FROM SNMPv2-TC;

stnModule MODULE-IDENTITY
    LAST-UPDATED "201703051300Z"
    ORGANIZATION ""
    CONTACT-INFO ""
    DESCRIPTION "MIB information for STN100"
  ::= { mib-2 1 }

-- Type Assignments ~~~~~~~~~~~~~~~~~~~~~~~~~~~~~~~~~~~~~~~~~~~~~~~~~~~~~~~~~~~~
Signed8 ::= TEXTUAL-CONVENTION
  STATUS current
  DESCRIPTION ""
  SYNTAX Integer32 ( -128..127 )

Signed16 ::= TEXTUAL-CONVENTION
  STATUS current
  DESCRIPTION ""
  SYNTAX Integer32 ( -32768..32767 )

Signed32 ::= TEXTUAL-CONVENTION
  STATUS current
  DESCRIPTION ""
  SYNTAX Integer32 ( -2147483648..2147483647 )

Unsigned8 ::= TEXTUAL-CONVENTION
  STATUS current
  DESCRIPTION ""
  SYNTAX Integer32 ( 0..255 )

Unsigned16 ::= TEXTUAL-CONVENTION
  STATUS current
  DESCRIPTION ""
  SYNTAX Integer32 ( 0..65535 )
  
Boolean ::= TEXTUAL-CONVENTION
  STATUS current
  DESCRIPTION ""
  SYNTAX INTEGER { false(0), true(1) }

Float ::= TEXTUAL-CONVENTION
  STATUS current
  DESCRIPTION ""
  SYNTAX Integer32 ( -2147483648..2147483647 )

TimeIntervalInSeconds ::= TimeTicks

TimeIntervalInMinutes ::= Integer32

TimeIntervalInDays ::= Integer32

Access-Level ::= INTEGER {
  read-Only(1),
  read-Write(2)
}

Enable-State ::= INTEGER {
  disabled(0),
  enabled(1)
}

Severity-Level ::= INTEGER {
  warnings-And-Above(1),
  minor-And-Above(2),
  major-And-Above(3),
  none(4),
  critical-Only(5)
}

SNMP-Trap-Version ::= INTEGER {
  snmp-V1-Trap(0),
  snmp-V2-Trap(1),
  snmp-V3-Trap(2)
}

Trap-Receiver-Mode ::= INTEGER {
  normal-Traps(1),
  acknowledged-Summary-Trap(2)
}

Alarm-Active-State ::= INTEGER {
  not-Active(0),
  active-Warning(1),
  active-Minor(2),
  active-Major(3),
  active-Critical(4),
  reserved(5)
}

Trap-Alarm-Keep-Severity ::= INTEGER {
  critical(1),
  major(2),
  minor(3),
  warning(4),
  cleared(5)
}

Alarm-Severity ::= INTEGER {
  disabled(0),
  critical(1),
  major(2),
  minor(3),
  warning(4),
  control(5)
}

System-Alarm ::= INTEGER {
	ac-Main-Fail(1),
	ac-Low-Voltage(2),
	dc-Low-Voltage(3),
	rectifier-Fail(4),
	rectifier-Current-Limit(5),
	rectifier-Short-Circuit(6),
	rectifier-Over-Temperature(7),
	dcDc1-Alarm(8),
	dcDc2-Alarm(9),
	dcDc3-Alarm(10),
	dcDc4-Alarm(11),
	dcDc5-Alarm(12),
	dcDc6-Alarm(13)
}

Active-State ::= INTEGER {
  normal(0),
  low(1),
  high(2)
}

Status-State ::= INTEGER {
  normal(0),
  lower-Limit(1),
  upper-Limit(2),
  other-Error(3)
}

YesNo-State ::= INTEGER {
  no(0),
  yes(1)
}

OnOff-State ::= INTEGER {
  off(0),
  on(1)
}

String-10 ::= TEXTUAL-CONVENTION
    STATUS       current
    DESCRIPTION  ""
    SYNTAX       OCTET STRING (SIZE(0..10))

String-20 ::= TEXTUAL-CONVENTION
    STATUS       current
    DESCRIPTION  ""
    SYNTAX       OCTET STRING (SIZE(0..20))

String-30 ::= TEXTUAL-CONVENTION
    STATUS       current
    DESCRIPTION  ""
    SYNTAX       OCTET STRING (SIZE(0..30))

String-40 ::= TEXTUAL-CONVENTION
    STATUS       current
    DESCRIPTION  ""
    SYNTAX       OCTET STRING (SIZE(0..40))

String-60 ::= TEXTUAL-CONVENTION
    STATUS       current
    DESCRIPTION  ""
    SYNTAX       OCTET STRING (SIZE(0..60))

MIB-Object-ID ::= TEXTUAL-CONVENTION
    STATUS       current
    DESCRIPTION  ""
    SYNTAX       OCTET STRING (SIZE(0..80))

String-253 ::= TEXTUAL-CONVENTION
    STATUS       current
    DESCRIPTION  ""
    SYNTAX       OCTET STRING (SIZE(0..253))

No-Data ::= TEXTUAL-CONVENTION
  STATUS current
  DESCRIPTION ""
  SYNTAX OCTET STRING(SIZE(0))
  
-- OID Value Assignment and OBJECT-TYPE Construct ~~~~~~~~~~~~~~~~~~~~~~~~~~~~
stu OBJECT IDENTIFIER ::= { enterprises 47865 }
ems OBJECT IDENTIFIER ::= { stu 3 }
stn OBJECT IDENTIFIER ::= { ems 10 }

stn-Objects OBJECT-IDENTITY
  STATUS current
  DESCRIPTION ""
 ::= { stn 10 }

system-Identity OBJECT-IDENTITY
  STATUS current
  DESCRIPTION ""
 ::= { stn-Objects 10 }

system-Manufacturer OBJECT-TYPE
  SYNTAX String-20
  MAX-ACCESS read-write
  STATUS current
  DESCRIPTION "The manufacturer of system."
  DEFVAL { "Sinergi Teknologi" }
::= { system-Identity 10 }

product-Serial-Number OBJECT-TYPE
  SYNTAX String-10
  MAX-ACCESS read-only
  STATUS current
  DESCRIPTION "System serial number assigned by the manufacturer."
  DEFVAL { "0000000000" }
::= { system-Identity 20 }

software-Version OBJECT-TYPE
  SYNTAX String-10
  MAX-ACCESS read-only
  STATUS current
  DESCRIPTION "System software version."
  DEFVAL { "1.0" }
::= { system-Identity 40 }

system-Type OBJECT-TYPE
  SYNTAX String-20
  MAX-ACCESS read-write
  STATUS current
  DESCRIPTION "System model number assigned by the manufacturer."
  DEFVAL { "STN100" }
::= { system-Identity 50 }

system-Location OBJECT-TYPE
  SYNTAX String-20
  MAX-ACCESS read-write
  STATUS current
  DESCRIPTION "Usually the location of site."
  DEFVAL { "Bandung" }
::= { system-Identity 60 }

site-ID OBJECT-TYPE
  SYNTAX String-40
  MAX-ACCESS read-write
  STATUS current
  DESCRIPTION "The site ID."
  DEFVAL { "Site ID" }
::= { system-Identity 70 }

site-Name OBJECT-TYPE
  SYNTAX String-40
  MAX-ACCESS read-write
  STATUS current
  DESCRIPTION "The site designation or code."
  DEFVAL { "Site Name" }
::= { system-Identity 80 }

site-Address OBJECT-TYPE
  SYNTAX String-40
  MAX-ACCESS read-write
  STATUS current
  DESCRIPTION "The street address of the site."
  DEFVAL { "Site Address" }
::= { system-Identity 90 }



communications OBJECT-IDENTITY
  STATUS current
  DESCRIPTION ""
 ::= { stn-Objects 20 }

ip-Address OBJECT-TYPE
  SYNTAX IpAddress
  MAX-ACCESS read-write
  STATUS current
  DESCRIPTION "The Internet Protocol (IP) address. This value and the Subnet Mask must be set correctly to communicate using Ethernet. Consult your network administrator."
  DEFVAL { "1.1.1.1" }
::= { communications 10 }

subnet-Mask OBJECT-TYPE
  SYNTAX IpAddress
  MAX-ACCESS read-write
  STATUS current
  DESCRIPTION "Identifies which fragment of the IP address is the sub-network identity. This value and the IP Address must be set correctly to communicate using Ethernet. Consult your network administrator."
  DEFVAL { "255.255.255.0" }
::= { communications 20 }

gateway-Address OBJECT-TYPE
  SYNTAX IpAddress
  MAX-ACCESS read-write
  STATUS current
  DESCRIPTION "Allows access to IP addresses outside your sub-network. Consult your network administrator."
  DEFVAL { "1.1.1.1" }
::= { communications 30 }


snmp OBJECT-IDENTITY
  STATUS current
  DESCRIPTION ""
 ::= { communications 40 }

snmp-Read-Community OBJECT-TYPE
  SYNTAX String-20
  MAX-ACCESS read-write
  STATUS current
  DESCRIPTION "Community that can get items."
  DEFVAL { "public" }
::= { snmp 10 }

snmp-Write-Community OBJECT-TYPE
  SYNTAX String-20
  MAX-ACCESS read-write
  STATUS current
  DESCRIPTION "Community that can set items."
  DEFVAL { "private" }
::= { snmp 20 }

enable-Trap-Repeat OBJECT-TYPE
  SYNTAX Enable-State
  MAX-ACCESS read-write
  STATUS current
  DESCRIPTION "If enabled, alarm activation traps will be repeated according to Trap Repeat Rate."
  DEFVAL { enabled }
::= { snmp 30 }

trap-Repeat-Rate OBJECT-TYPE
  SYNTAX TimeIntervalInMinutes
  UNITS "min"
  MAX-ACCESS read-write
  STATUS current
  DESCRIPTION "How often to send a trap to trap receivers if Enable Trap Repeat is Enabled or the trap receiver's Trap Receiver Mode is Acknowledged Summary Trap."
  DEFVAL { 1 }
::= { snmp 40 }

snmp-Trap-Receiver-Table OBJECT-TYPE
  SYNTAX SEQUENCE OF SNMP-Trap-Receiver-Entry
  MAX-ACCESS not-accessible
  STATUS current
  DESCRIPTION ""
::= { snmp 50 }

snmp-Trap-Receiver-Entry OBJECT-TYPE
  SYNTAX SNMP-Trap-Receiver-Entry
  MAX-ACCESS not-accessible
  STATUS current
  DESCRIPTION ""
  INDEX  { snmp-Trap-Receiver-Index }
::= { snmp-Trap-Receiver-Table 1 }

SNMP-Trap-Receiver-Entry ::= SEQUENCE {
  snmp-Trap-Receiver-Index Unsigned8,
  trap-Receiver-IP-Address IpAddress,
  trap-Receiver-Port Unsigned16,
  trap-Receiver-Name String-20,
  trap-Receiver-Level Severity-Level,
  trap-Receiver-Community String-20,
  trap-Receiver-Mode Trap-Receiver-Mode,
  acknowledge-Alarm-Summary-Trap No-Data
}

snmp-Trap-Receiver-Index OBJECT-TYPE
  SYNTAX Unsigned8
  MAX-ACCESS read-only
  STATUS current
  DESCRIPTION "Automatically generated index object."
::= { snmp-Trap-Receiver-Entry 1 }


trap-Receiver-IP-Address OBJECT-TYPE
  SYNTAX IpAddress
  MAX-ACCESS read-write
  STATUS current
  DESCRIPTION "SNMP notifications of events are sent to this IP address."
  DEFVAL { "1.1.1.1" }
::= { snmp-Trap-Receiver-Entry 20 }

trap-Receiver-Port OBJECT-TYPE
  SYNTAX Unsigned16
  MAX-ACCESS read-write
  STATUS current
  DESCRIPTION "SNMP notifications of events are sent to this UDP port."
  DEFVAL { 162 }
::= { snmp-Trap-Receiver-Entry 30 }

trap-Receiver-Name OBJECT-TYPE
  SYNTAX String-20
  MAX-ACCESS read-write
  STATUS current
  DESCRIPTION "Name used to identify the receiver."
  DEFVAL { "" }
::= { snmp-Trap-Receiver-Entry 40 }

trap-Receiver-Level OBJECT-TYPE
  SYNTAX Severity-Level
  MAX-ACCESS read-write
  STATUS current
  DESCRIPTION "Sets the severity of alarms to be reported to this trap receiver."
  DEFVAL { none }
::= { snmp-Trap-Receiver-Entry 50 }

trap-Receiver-Community OBJECT-TYPE
  SYNTAX String-20
  MAX-ACCESS read-write
  STATUS current
  DESCRIPTION "Community to use for traps sent to the receiver."
  DEFVAL { "public" }
::= { snmp-Trap-Receiver-Entry 60 }

trap-Receiver-Mode OBJECT-TYPE
  SYNTAX Trap-Receiver-Mode
  MAX-ACCESS read-write
  STATUS current
  DESCRIPTION "Set to Normal traps to send normal traps to a Network Management System on alarm activation and deactivation. Set to Acknowledged Summary Traps to send summary traps to PowerManagerII. These traps are repeated until PowerManagerII receives the trap, connects to the controller, and downloads alarms and data."
  DEFVAL { normal-Traps }
::= { snmp-Trap-Receiver-Entry 70 }

acknowledge-Alarm-Summary-Trap OBJECT-TYPE
  SYNTAX No-Data
  MAX-ACCESS read-write
  STATUS current
  DESCRIPTION "This command will acknowledge reception of the alarm summary trap."
::= { snmp-Trap-Receiver-Entry 80 }

interval OBJECT-IDENTITY
  STATUS current
  DESCRIPTION ""
 ::= { communications 50 }
 
alarm-Trap-Interval OBJECT-TYPE
  SYNTAX Integer
  MAX-ACCESS read-write
  STATUS current
  DESCRIPTION ""
::= { interval 10 }

datalog-Interval OBJECT-TYPE
  SYNTAX Integer
  MAX-ACCESS read-write
  STATUS current
  DESCRIPTION ""
::= { interval 20 }


analog-Input OBJECT-IDENTITY
  STATUS current
  DESCRIPTION ""
 ::= { stn-Objects 30 }
 
analog-Voltage OBJECT-TYPE
  SYNTAX Integer
  MAX-ACCESS read-only
  STATUS current
  DESCRIPTION ""
  UNITS "V"
  DEFVAL { "" }
::= { analog-Input 10 }

analog-Current1 OBJECT-TYPE
  SYNTAX Integer
  MAX-ACCESS read-only
  STATUS current
  DESCRIPTION ""
  UNITS "A"
  DEFVAL { "" }
::= { analog-Input 20 }

analog-Current2 OBJECT-TYPE
  SYNTAX Integer
  MAX-ACCESS read-only
  STATUS current
  DESCRIPTION ""
  UNITS "A"
  DEFVAL { "" }
::= { analog-Input 30 }

analog-Current3 OBJECT-TYPE
  SYNTAX Integer
  MAX-ACCESS read-only
  STATUS current
  DESCRIPTION ""
  UNITS "A"
  DEFVAL { "" }
::= { analog-Input 40 }


digital-Input OBJECT-IDENTITY
  STATUS current
  DESCRIPTION ""
 ::= { stn-Objects 40 }

digital-Input-1 OBJECT-TYPE
  SYNTAX Integer
  MAX-ACCESS read-only
  STATUS current
  DESCRIPTION "1=Active, 0=NA"
  UNITS ""
  DEFVAL { "" }
::= { digital-Input 10 }

digital-Input-2 OBJECT-TYPE
  SYNTAX Integer
  MAX-ACCESS read-only
  STATUS current
  DESCRIPTION "1=Active, 0=NA"
  UNITS ""
  DEFVAL { "" }
::= { digital-Input 20 }

digital-Input-3 OBJECT-TYPE
  SYNTAX Integer
  MAX-ACCESS read-only
  STATUS current
  DESCRIPTION "1=Active, 0=NA"
  UNITS ""
  DEFVAL { "" }
::= { digital-Input 30 }

digital-Input-4 OBJECT-TYPE
  SYNTAX Integer
  MAX-ACCESS read-only
  STATUS current
  DESCRIPTION "1=Active, 0=NA"
  UNITS ""
  DEFVAL { "" }
::= { digital-Input 40 }

digital-Input-5 OBJECT-TYPE
  SYNTAX Integer
  MAX-ACCESS read-only
  STATUS current
  DESCRIPTION "1=Active, 0=NA"
  UNITS ""
  DEFVAL { "" }
::= { digital-Input 50 }

digital-Input-6 OBJECT-TYPE
  SYNTAX Integer
  MAX-ACCESS read-only
  STATUS current
  DESCRIPTION "1=Active, 0=NA"
  UNITS ""
  DEFVAL { "" }
::= { digital-Input 60 }

digital-Input-7 OBJECT-TYPE
  SYNTAX Integer
  MAX-ACCESS read-only
  STATUS current
  DESCRIPTION "1=Active, 0=NA"
  UNITS ""
  DEFVAL { "" }
::= { digital-Input 70 }

digital-Input-8 OBJECT-TYPE
  SYNTAX Integer
  MAX-ACCESS read-only
  STATUS current
  DESCRIPTION "1=Active, 0=NA"
  UNITS ""
  DEFVAL { "" }
::= { digital-Input 80 }

temperature-Humidity OBJECT-IDENTITY
  STATUS current
  DESCRIPTION ""
 ::= { stn-Objects 50 }
 
temperature OBJECT-TYPE
  SYNTAX Integer
  MAX-ACCESS read-only
  STATUS current
  DESCRIPTION ""
  UNITS "C"
  DEFVAL { "" }
::= { temperature-Humidity 10 }

humidity OBJECT-TYPE
  SYNTAX Integer
  MAX-ACCESS read-only
  STATUS current
  DESCRIPTION ""
  UNITS "%"
  DEFVAL { "" }
::= { temperature-Humidity 20 }


morning-Up OBJECT-IDENTITY
  STATUS current
  DESCRIPTION ""
 ::= { stn-Objects 60 }

voltage-Input OBJECT-TYPE
  SYNTAX Integer
  MAX-ACCESS read-only
  STATUS current
  DESCRIPTION ""
  UNITS "V"
  DEFVAL { "" }
::= { morning-Up 10 }
 
current-Input OBJECT-TYPE
  SYNTAX Integer
  MAX-ACCESS read-only
  STATUS current
  DESCRIPTION ""
  UNITS "A"
  DEFVAL { "" }
::= { morning-Up 20 }
 
voltage-Output OBJECT-TYPE
  SYNTAX Integer
  MAX-ACCESS read-only
  STATUS current
  DESCRIPTION ""
  UNITS "V"
  DEFVAL { "" }
::= { morning-Up 30 }

current-Output OBJECT-TYPE
  SYNTAX Integer
  MAX-ACCESS read-only
  STATUS current
  DESCRIPTION ""
  UNITS "A"
  DEFVAL { "" }
::= { morning-Up 40 }

power-Output OBJECT-TYPE
  SYNTAX Integer
  MAX-ACCESS read-only
  STATUS current
  DESCRIPTION ""
  UNITS "W"
  DEFVAL { "" }
::= { morning-Up 50 }


digital-Output OBJECT-IDENTITY
  STATUS current
  DESCRIPTION ""
 ::= { stn-Objects 70 }

digital-Output-1 OBJECT-TYPE
  SYNTAX Integer
  MAX-ACCESS write-only
  STATUS current
  DESCRIPTION ""
  UNITS ""
  DEFVAL { "" }
::= { digital-Output 10 }

digital-Output-2 OBJECT-TYPE
  SYNTAX Integer
  MAX-ACCESS write-only
  STATUS current
  DESCRIPTION ""
  UNITS ""
  DEFVAL { "" }
::= { digital-Output 20 }





-- alarm 
alarm OBJECT-IDENTITY
  STATUS current
  DESCRIPTION ""
 ::= { stn-Objects 90 }

summary-Alarm-Critical OBJECT-TYPE
  SYNTAX Unsigned8
  MAX-ACCESS read-only
  STATUS current
  DESCRIPTION ""
::= { alarm 10 }
 
summary-Alarm-Major OBJECT-TYPE
  SYNTAX Unsigned8
  MAX-ACCESS read-only
  STATUS current
  DESCRIPTION ""
::= { alarm 20 }

summary-Alarm-Minor OBJECT-TYPE
  SYNTAX Unsigned8
  MAX-ACCESS read-only
  STATUS current
  DESCRIPTION ""
::= { alarm 30 }

summary-Alarm-Warning OBJECT-TYPE
  SYNTAX Unsigned8
  MAX-ACCESS read-only
  STATUS current
  DESCRIPTION ""
::= { alarm 40 }

alarm-Table OBJECT-TYPE
  SYNTAX SEQUENCE OF Alarm-Entry
  MAX-ACCESS not-accessible
  STATUS current
  DESCRIPTION ""
::= { alarm 50 }

alarm-Entry OBJECT-TYPE
  SYNTAX Alarm-Entry
  MAX-ACCESS not-accessible
  STATUS current
  DESCRIPTION ""
  INDEX  { alarm-Index }
::= { alarm-Table 1 }

Alarm-Entry ::= SEQUENCE {
  alarm-Index System-Alarm,
  alarm-Severity Alarm-Severity,
  alarm-State Active-State
}

alarm-Index OBJECT-TYPE
  SYNTAX System-Alarm
  MAX-ACCESS read-only
  STATUS current
  DESCRIPTION "Index of alarm"
::= { alarm-Entry 10 }

alarm-Severity OBJECT-TYPE
  SYNTAX Alarm-Severity
  MAX-ACCESS read-write
  STATUS current
  DESCRIPTION "The severity level associated with the alarm. Control alarms are not displayed, although any configured digital outputs are still activated."
  DEFVAL { major }
::= { alarm-Entry 20 }

alarm-State OBJECT-TYPE
  SYNTAX Active-State
  MAX-ACCESS read-only
  STATUS current
  DESCRIPTION "The state of this alarm."
::= { alarm-Entry 30 }

-- end of alarms


-- setting 
setting OBJECT-IDENTITY
  STATUS current
  DESCRIPTION ""
 ::= { stn-Objects 100 }

analog-Input-Setting OBJECT-IDENTITY
  STATUS current
  DESCRIPTION ""
::= { setting 10 }

voltage-High-Treshold OBJECT-TYPE
  SYNTAX Integer
  MAX-ACCESS read-write
  STATUS current
  UNITS "V"
  DESCRIPTION ""
::= { analog-Input-Setting 10 }

voltage-Low-Treshold OBJECT-TYPE
  SYNTAX Integer
  MAX-ACCESS read-write
  STATUS current
  UNITS "V"
  DESCRIPTION ""
::= { analog-Input-Setting 20 }

voltage-Scale OBJECT-TYPE
  SYNTAX Integer
  MAX-ACCESS read-write
  STATUS current
  UNITS "V"
  DESCRIPTION ""
::= { analog-Input-Setting 30 }

current1-High-Treshold OBJECT-TYPE
  SYNTAX Integer
  MAX-ACCESS read-write
  STATUS current
  UNITS "A"
  DESCRIPTION ""
::= { analog-Input-Setting 40 }

current1-Low-Treshold OBJECT-TYPE
  SYNTAX Integer
  MAX-ACCESS read-write
  STATUS current
  UNITS "A"
  DESCRIPTION ""
::= { analog-Input-Setting 50 }

current1-Scale OBJECT-TYPE
  SYNTAX Integer
  MAX-ACCESS read-write
  STATUS current
  UNITS "A"
  DESCRIPTION ""
::= { analog-Input-Setting 60 }

current2-High-Treshold OBJECT-TYPE
  SYNTAX Integer
  MAX-ACCESS read-write
  STATUS current
  UNITS "A"
  DESCRIPTION ""
::= { analog-Input-Setting 70 }

current2-Low-Treshold OBJECT-TYPE
  SYNTAX Integer
  MAX-ACCESS read-write
  STATUS current
  UNITS "A"
  DESCRIPTION ""
::= { analog-Input-Setting 80 }

current2-Scale OBJECT-TYPE
  SYNTAX Integer
  MAX-ACCESS read-write
  STATUS current
  UNITS "A"
  DESCRIPTION ""
::= { analog-Input-Setting 90 }

current3-High-Treshold OBJECT-TYPE
  SYNTAX Integer
  MAX-ACCESS read-write
  STATUS current
  UNITS "A"
  DESCRIPTION ""
::= { analog-Input-Setting 100 }

current3-Low-Treshold OBJECT-TYPE
  SYNTAX Integer
  MAX-ACCESS read-write
  STATUS current
  UNITS "A"
  DESCRIPTION ""
::= { analog-Input-Setting 110 }

current3-Scale OBJECT-TYPE
  SYNTAX Integer
  MAX-ACCESS read-write
  STATUS current
  UNITS "A"
  DESCRIPTION ""
::= { analog-Input-Setting 120 }


digital-Input-Setting OBJECT-IDENTITY
  STATUS current
  DESCRIPTION ""
::= { setting 20 }

digital-Input1-State OBJECT-TYPE
  SYNTAX INTEGER { enabled(1), disabled(0) }
  MAX-ACCESS read-write
  STATUS current
  DESCRIPTION "1=Enabled, 0=Disabled"
::= { digital-Input-Setting 10 }

digital-Input1-Trigger OBJECT-TYPE
  SYNTAX INTEGER { high(1), low(0) }
  MAX-ACCESS read-write
  STATUS current
  DESCRIPTION "1=High, 0=Low"
::= { digital-Input-Setting 20 }

digital-Input2-State OBJECT-TYPE
  SYNTAX INTEGER { enabled(1), disabled(0) }
  MAX-ACCESS read-write
  STATUS current
  DESCRIPTION "1=Enabled, 0=Disabled"
::= { digital-Input-Setting 30 }

digital-Input2-Trigger OBJECT-TYPE
  SYNTAX INTEGER { high(1), low(0) }
  MAX-ACCESS read-write
  STATUS current
  DESCRIPTION "1=High, 0=Low"
::= { digital-Input-Setting 40 }

digital-Input3-State OBJECT-TYPE
  SYNTAX INTEGER { enabled(1), disabled(0) }
  MAX-ACCESS read-write
  STATUS current
  DESCRIPTION "1=Enabled, 0=Disabled"
::= { digital-Input-Setting 50 }

digital-Input3-Trigger OBJECT-TYPE
  SYNTAX INTEGER { high(1), low(0) }
  MAX-ACCESS read-write
  STATUS current
  DESCRIPTION "1=High, 0=Low"
::= { digital-Input-Setting 60 }

digital-Input4-State OBJECT-TYPE
  SYNTAX INTEGER { enabled(1), disabled(0) }
  MAX-ACCESS read-write
  STATUS current
  DESCRIPTION "1=Enabled, 0=Disabled"
::= { digital-Input-Setting 70 }

digital-Input4-Trigger OBJECT-TYPE
  SYNTAX INTEGER { high(1), low(0) }
  MAX-ACCESS read-write
  STATUS current
  DESCRIPTION "1=High, 0=Low"
::= { digital-Input-Setting 80 }

digital-Input5-State OBJECT-TYPE
  SYNTAX INTEGER { enabled(1), disabled(0) }
  MAX-ACCESS read-write
  STATUS current
  DESCRIPTION "1=Enabled, 0=Disabled"
::= { digital-Input-Setting 90 }

digital-Input5-Trigger OBJECT-TYPE
  SYNTAX INTEGER { high(1), low(0) }
  MAX-ACCESS read-write
  STATUS current
  DESCRIPTION "1=High, 0=Low"
::= { digital-Input-Setting 100 }

digital-Input6-State OBJECT-TYPE
  SYNTAX INTEGER { enabled(1), disabled(0) }
  MAX-ACCESS read-write
  STATUS current
  DESCRIPTION "1=Enabled, 0=Disabled"
::= { digital-Input-Setting 110 }

digital-Input6-Trigger OBJECT-TYPE
  SYNTAX INTEGER { high(1), low(0) }
  MAX-ACCESS read-write
  STATUS current
  DESCRIPTION "1=High, 0=Low"
::= { digital-Input-Setting 120 }

digital-Input7-State OBJECT-TYPE
  SYNTAX INTEGER { enabled(1), disabled(0) }
  MAX-ACCESS read-write
  STATUS current
  DESCRIPTION "1=Enabled, 0=Disabled"
::= { digital-Input-Setting 130 }

digital-Input7-Trigger OBJECT-TYPE
  SYNTAX INTEGER { high(1), low(0) }
  MAX-ACCESS read-write
  STATUS current
  DESCRIPTION "1=High, 0=Low"
::= { digital-Input-Setting 140 }

digital-Input8-State OBJECT-TYPE
  SYNTAX INTEGER { enabled(1), disabled(0) }
  MAX-ACCESS read-write
  STATUS current
  DESCRIPTION "1=Enabled, 0=Disabled"
::= { digital-Input-Setting 150 }

digital-Input8-Trigger OBJECT-TYPE
  SYNTAX INTEGER { high(1), low(0) }
  MAX-ACCESS read-write
  STATUS current
  DESCRIPTION "1=High, 0=Low"
::= { digital-Input-Setting 160 }


digital-Output-Setting OBJECT-IDENTITY
  STATUS current
  DESCRIPTION ""
::= { setting 30 }

digital-Output1-State OBJECT-TYPE
  SYNTAX INTEGER { enabled(1), disabled(0) }
  MAX-ACCESS read-write
  STATUS current
  DESCRIPTION "1=Enabled, 0=Disabled"
::= { digital-Output-Setting 10 }

digital-Output1-Control OBJECT-TYPE
  SYNTAX INTEGER { on(1), off(0) }
  MAX-ACCESS read-write
  STATUS current
  DESCRIPTION "1=On, 0=Off"
::= { digital-Output-Setting 20 }

digital-Output2-State OBJECT-TYPE
  SYNTAX INTEGER { enabled(1), disabled(0) }
  MAX-ACCESS read-write
  STATUS current
  DESCRIPTION "1=Enabled, 0=Disabled"
::= { digital-Output-Setting 10 }

digital-Output2-Control OBJECT-TYPE
  SYNTAX INTEGER { on(1), off(0) }
  MAX-ACCESS read-write
  STATUS current
  DESCRIPTION "1=On, 0=Off"
::= { digital-Output-Setting 20 }



temp-Humi-Setting OBJECT-IDENTITY
  STATUS current
  DESCRIPTION ""
::= { setting 40 }

temp-High-Treshold OBJECT-TYPE
  SYNTAX Integer
  MAX-ACCESS read-write
  STATUS current
  UNITS "C"
  DESCRIPTION ""
::= { temp-Humi-Setting 10 }

temp-Scale OBJECT-TYPE
  SYNTAX Integer
  MAX-ACCESS read-write
  STATUS current
  UNITS "C"
  DESCRIPTION ""
::= { temp-Humi-Setting 20 }

humi-High-Treshold OBJECT-TYPE
  SYNTAX Integer
  MAX-ACCESS read-write
  STATUS current
  UNITS "%"
  DESCRIPTION ""
::= { temp-Humi-Setting 30 }

humi-Scale OBJECT-TYPE
  SYNTAX Integer
  MAX-ACCESS read-write
  STATUS current
  UNITS "%"
  DESCRIPTION ""
::= { temp-Humi-Setting 40 }

-- end of setting



-- traps object
stn-Traps OBJECT-IDENTITY
  STATUS current
  DESCRIPTION ""
 ::= { stn 20 }

psu-Global-Traps NOTIFICATION-TYPE
  OBJECTS { alarm-Index, alarm-State }
  STATUS current
  DESCRIPTION "An alarm has changed state."
::= { stn-Traps 1000 }

END
